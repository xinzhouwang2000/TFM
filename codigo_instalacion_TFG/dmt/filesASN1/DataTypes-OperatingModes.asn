------------------------------------------------------------------------------
--                                                                          --
--          Copyright (C) 2022 Universidad Politécnica de Madrid           --
--                                                                          --
--                          H E R C C U L E S                               --
--                                                                          --
--                        Operating modes Types                             --
--                                                                          --
-- This is free software;  you can redistribute it  and/or modify it  under --
-- terms of the  GNU General Public License as published  by the Free Soft- --
-- ware  Foundation;  either version 3,  or (at your option) any later ver- --
-- sion.  This software is distributed in the hope  that it will be useful, --
-- but WITHOUT ANY WARRANTY;  without even the implied warranty of MERCHAN- --
-- TABILITY or FITNESS FOR A PARTICULAR PURPOSE. See the GNU General Public --
-- License for  more details.  You should have  received  a copy of the GNU --
-- General  Public  License  distributed  with  this  software;   see  file --
-- COPYING3.  If not, go to http://www.gnu.org/licenses for a complete copy --
-- of the license.                                                          --
--                                                                          --
------------------------------------------------------------------------------


DataTypes-OperatingModes DEFINITIONS ::= BEGIN

    ----------------------------------------------------------------------------
    -- Operating Modes:
    --
    -- * HERCCULES has different operating modes, defined in "Balloon Mode".
    -- * HERCCULES is composed of five SUBSYSTEMS, each one with their own
    --     operating modes defined in further data types.
    -- * Optionaly, SUBSYSTEMS may include EXPERIMENTS that are controlled
    --     automatically or through TCs, namely: autonomous and operator modes.
    --
    -- Note: The experiments modes are embedded in the subsystems' modes
    --       definition for simplicity.
    ----------------------------------------------------------------------------

    --  Balloon Mode  ----------------------------------------------------------

    -- System wide mode for the HERCCULES experiment.
    Balloon-Mode ::= ENUMERATED {
        -- Ground --
        ground-await,
        ground-pre-launch,

        -- Flight --
        flight-ascent,
        flight-float,

        -- OFF --
        off
    }    

    --  Subsystem Modes  -------------------------------------------------------

    ---------------------------------
    -- Heat Transfer Lab subsystem --
    ---------------------------------

    HTL-Mode ::= SEQUENCE {
        -- HTL, subsystem level mode --
        mode ENUMERATED {
            off,
            pre-launch,

            ascent-mode1,
            ascent-mode2,

            float-mode1,
            float-mode2,
            float-mode3
        },

        -- Modes for each HTL heater --
        heaters-mode HTL-Heaters-Mode
    }

    HTL-Heaters-Mode ::= SEQUENCE {
        experiment-1 Actuator-Control-Mode,
        experiment-2 Actuator-Control-Mode,
        experiment-3 Actuator-Control-Mode,
        experiment-4 Actuator-Control-Mode
    }

    -----------------------
    -- Environmental Lab --
    -----------------------

    Env-Lab-Mode ::= SEQUENCE {
        mode ENUMERATED {
            off,
            on
        },

        heaters-mode Env-Lab-Heaters-Mode
    }

    Env-Lab-Heaters-Mode ::= SEQUENCE {
        upwards    Actuator-Control-Mode,
        downwards  Actuator-Control-Mode
    }

    ------------------
    -- Attitude Lab --
    ------------------

    Att-Lab-Mode ::= ENUMERATED {
        off,
        on
    }

    --------------------------
    -- Power & Control Unit --
    --------------------------

    PCU-Mode ::= ENUMERATED {
        off,
        on
    }

    -----------------------------------------------------
    -- Navigational & Attitude Determination Subsystem --
    -----------------------------------------------------

    NADS-Mode ::= ENUMERATED {
        off,
        on
    }

    ---------------------------------------
    -- Telemetry & Telecommand Subsystem --
    ---------------------------------------

    TMTC-Mode ::= ENUMERATED { -- When:
        nominal,     --+ connection is active and bandwidth is FINE
        degraded,    --+ connection is active but bandwidth is LOW
        mute         --+ connection may be active and the bandwidth is TOO LOW
    }

    --  A U X I L I A R Y  -----------------------------------------------------

    ---------------------------
    -- Actuator Control Mode --
    ---------------------------

    -- This auxiliary type defines the ways an actuator (e.g.: heater or switch)
    -- can be controlled.

    Actuator-Control-Mode ::= ENUMERATED {
        autonomous-control,  -- An experiment is either controlled AUTOMATICALLY
        manual-control       -- or MANUALLY by the operator through telecommands
    }

END
